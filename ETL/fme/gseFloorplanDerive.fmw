FME workspace gseFloorplanDerive.fmw
Title: GizintaLoader
Description: First Beta release of Gizinta for FME
Usage: Add the xml file and other parameters
Requirements: test
History: 31/10/2013,support@Gizinta.com,First Draft
Legal terms conditions: This work is licensed under the Creative Commons Attribution-ShareAlike 3.0 Unported License.
Startup Python:
      import xml.dom.minidom
      import os
      import sys
      import time
      import fmeobjects

      ospath = FME_MacroValues['FME_MF_DIR']
      print ospath
      if ospath not in sys.path:
          sys.path.append(ospath)
      import gzfme

      ErrorUniqueID = "ErrorUniqueID"
      ErrorRequiredValue = "ErrorRequiredValue"
      ErrorValueMap = "ErrorValueMap"
      Errors = False

      debug = gzfme.setDebug(FME_MacroValues['gzDebug'])
      logger = fmeobjects.FMELogFile()
      gzfme.logger = logger
Shutdown Python:
      import fmeobjects, gzfme

      gzfme.shutdown(Errors,str(FME_MacroValues['IgnoreErrors']),FME_TotalFeaturesWritten,FME_MacroValues)

      del Errors
      del ErrorUniqueID
      del ErrorRequiredValue
      del ErrorValueMap
      del debug
      del logger
      gzfme.logger = None

Parameters:
- DestDataset_GEODATABASE_SDE = sde   # Destination Esri ArcSDE Geodatabase Dataset
- OUT_CONNECTION_FILE_GEODATABASE_SDE = C:\Apps\Gizinta\gseVT\ETL\serverConfig\GIS Staging.sde   # Connection File
- ProductionConnectionFile = C:\apps\Gizinta\gseVT\ETL\serverConfig\GIS Production.sde   # Enter the path and name of the Production SDE Database connection file
- GizintaProject = C:\apps\Gizinta\gseVT\ETL\config\fpDerivePlaylist.xml   # Select the Gizinta Xml File to use
- SourceFieldQA = False   # Choose whether to perform QA on Source Fields
- TargetFieldQA = True   # Choose whether to perform QA on Target Fields
- IgnoreErrors = False   # Ignore Errors and continue
- SourceDatasetTypes = GDBDataset   # Enter the Gizinta Source Dataset Type
- bldg =   # Building ID
- flr = MC_0004_02   # Enter the FLOORID
- gzDebug = False   # Enable gzDebug (True/False)
- LOG_FILE =   # Log File
- FEATURE_TYPES = InteriorSpace_Tilt FloorplanLine InteriorSpace Floor_Outline Floor_Point Floor_Poly FloorplanLine_Publish Floor_Area InteriorSpace_Point   # Feature Types to Write
- FEATURE_TYPES_READ = Floor_Area Floor_Poly InteriorSpace FloorplanLine
- SourceDataset_GEODATABASE_SDE = sde   # Source Esri ArcSDE Geodatabase Dataset
- FEATURE_TYPES_2 = Building_Outline_Point Building_Outline_Tilt Active_Floor Floor_Level Building_Outline_Point
- truncate = Y   # Truncate before load option
- fieldStyle = lowercase   # Enter field name style uppercase or lowercase

Readers:
- GEODATABASE_SDE_1: GEODATABASE_SDE from $(DestDataset_GEODATABASE_SDE)
- GEODATABASE_SDE_2: GEODATABASE_SDE from $(DestDataset_GEODATABASE_SDE)
- GEODATABASE_SDE_3: GEODATABASE_SDE from $(SourceDataset_GEODATABASE_SDE)

Writers:
- GEODATABASE_SDE_4: GEODATABASE_SDE to $(DestDataset_GEODATABASE_SDE)

DBO.Floor_Area (reader GEODATABASE_SDE_2)
    attributes: geodb_oid integer, OBJECTID integer, SITEID char(60), BUILDINGID char(60), FLOOR char(20), FLOORID char(60), FLOOR_AREA double, SCHELEV smallint, ALTITUDE smallint, SENSITIVITY char(20), SOURCEDWG char(60), IN_DATE date, LAST_USER char(30), GlobalID char(38), FLOOR_NAME char(60), BLDG_NAME char(60), SHAPE.STArea() double, SHAPE.STLength() double
    -> AttributeExposer_2
AttributeExposer_2
    ATTR_LIST = DRAWING,fme_feature_type,SPACEID,spaceid,floorid,buildingid
    -> TestLowerCase
TestLowerCase: Tester
    TEST_MODE = Automatic
    TEST_DESCRIPTION = ""
    BOOL_OP = OR
    TEST_CLAUSE = TEST $(fieldStyle) = lowercase
    FAILED -> TestFeatureTypes
    PASSED -> tolower
Note: change field names if not lowercase from source
tolower: BulkAttributeRenamer
    CASE_CHANGE_TYPE = lowercase
    ATTRCHOICE = All Attributes
    PATTERN_ACTION_DISP = Change Case
    -> TestFeatureTypes
TestFeatureTypes: Tester
    TEST_MODE = Automatic
    TEST_DESCRIPTION = ""
    BOOL_OP = OR
    TEST_CLAUSE = TEST $(FEATURE_TYPES_READ) CONTAINS @Value(fme_feature_type)
    PASSED -> TestFLOORID
TestFLOORID: Tester
    TEST_MODE = Automatic
    TEST_DESCRIPTION = ""
    BOOL_OP = OR
    TEST_CLAUSE = TEST @Value(floorid) = $(flr)
    PASSED -> BulkAttributeRenamer_2
BulkAttributeRenamer_2
    CASE_CHANGE_TYPE = lowercase
    ATTRCHOICE = All Attributes
    PATTERN_ACTION_DISP = Change Case
    -> FeatureMerger [input 1]
Building_Outline_Point (reader GEODATABASE_SDE_3)
    attributes: geodb_oid integer, OBJECTID integer, SITEID char(60), BUILDINGID char(60), CALCROT double, NUMFLOORS integer, SOURCEDWG char(60), SCALE_85X11 double, SCALE_11X17 double, SENSITIVITY char(20), IN_DATE date, LAST_USER char(30), GlobalID char(38), ALTITUDE double, SOURCEID char(30), DWG_NAME char(255), FLOOR char(6), INTERIORSPACE char(255), NAME_LONG char(255), BLDGHEIGHT double, FLOOR_LEVEL integer, SCHELEV integer, SHAPE.STLength() double, MARGIN double, FLOORPLANLINE char(255), YCENTER double, SHAPE.STArea() double, XCENTER double, FLOORID char(20), SPACING double,
      NAME_SHORT char(255)
    -> AttributeExposer_3
AttributeExposer_3
    ATTR_LIST = DRAWING,fme_feature_type,buildingid
    -> TestFieldCase_3
Note: setup building and floor data
TestFieldCase_3: Tester
    TEST_MODE = Automatic
    TEST_DESCRIPTION = ""
    BOOL_OP = OR
    TEST_CLAUSE = TEST $(fieldStyle) = lowercase
    PASSED -> tolower_2
    FAILED -> gseGetBldgFloorInfo
tolower_2: BulkAttributeRenamer
    CASE_CHANGE_TYPE = lowercase
    ATTRCHOICE = All Attributes
    PATTERN_ACTION_DISP = Change Case
    -> gseGetBldgFloorInfo
gseGetBldgFloorInfo
    bldg = $(bldg)
    flr = $(flr)
    FeatureMerger_3_Merged -> FeatureMerger [input 2]
FeatureMerger
    PROCESS_DUPS = No
    MERGE_TYPE = Attributes Only
    SUPPLIERS_FIRST = No
    JOIN_KEYS = @Value(floorid) @Value(floorid) AUTO
    SUPPLIER_PREFIX_DUMMY = YES
    MERGED -> TestFilter
TestFilter
    TEST_LIST:
      BOOL_OP,OR,COMPOSITE_TEST,<Unused>,TEST_CLAUSE,"TEST @Value(fme_feature_type) = FloorplanLine
      TEST @Value(fme_feature_type) = DBO.FloorplanLine",FloorplanLine,BOOL_OP,OR,COMPOSITE_TEST,<Unused>,TEST_CLAUSE,"TEST @Value(fme_feature_type) = InteriorSpace
      TEST @Value(fme_feature_type) = DBO.InteriorSpace",InteriorSpace,BOOL_OP,OR,COMPOSITE_TEST,<Unused>,TEST_CLAUSE,"TEST @Value(fme_feature_type) = Floor_Area
      TEST @Value(fme_feature_type) = DBO.Floor_Area",Floor_Area
    DEFAULT_VALUE = <UNFILTERED>
    FloorplanLine -> gzAggregateLines
    InteriorSpace -> InsidePointReplacer
    InteriorSpace -> gzTiltRooms
    Floor_Area -> GeometryReplacer
gzAggregateLines
    -> Bufferer
    -> FloorplanLine_Publish
Bufferer
    INTERP_SEGMENTS = 8
    OFFSET = 1
    CAP_STYLE = Round
    BUFFERED -> HullReplacer
HullReplacer
    HULLTYPE_PARAM = Convex ()
    HULL -> Floor_Outline
Floor_Outline: AttributeCreator
    ATTR_LIST = fme_feature_type,Floor_Outline
    -> AttributeCreator_3
FloorplanLine_Publish: AttributeCreator
    ATTR_LIST = fme_feature_type,FloorplanLine_Publish
    -> AttributeCreator_3
gzTiltRooms
    pFLOORID = $(flr)
    tiltHeight = 2
    -> gzFixIntersections
gzFixIntersections
    Feature_Type = InteriorSpace
    Tolerance = 0.001
    UniqueIDName = @Value(spaceid)
    -> InteriorSpace_Tilt
InteriorSpace_Tilt: AttributeCreator
    ATTR_LIST = fme_feature_type,InteriorSpace_Tilt
    -> AttributeCreator_3
InsidePointReplacer
    INSIDEPOINT -> InteriorSpace_Point
InteriorSpace_Point: AttributeCreator
    ATTR_LIST = fme_feature_type,InteriorSpace_Point
    -> AttributeCreator_3
GeometryReplacer
    SOURCE = @Value(_geometry)
    REMOVE_ATTRIBUTE = No
    KIND_LONG = FME Binary
    -> Floor_Point
Floor_Point: AttributeCreator
    ATTR_LIST = fme_feature_type,Floor_Point
    -> AttributeCreator_3
AttributeCreator_3
    ATTR_LIST = DRAWING,$(flr)
    -> TestLowerCase_2
TestLowerCase_2: Tester
    TEST_MODE = Automatic
    TEST_DESCRIPTION = ""
    BOOL_OP = OR
    TEST_CLAUSE = TEST $(fieldStyle) = lowercase
    PASSED -> gzFieldCalculator
    FAILED -> toupper
toupper: BulkAttributeRenamer
    CASE_CHANGE_TYPE = UPPERCASE
    ATTRCHOICE = All Attributes
    PATTERN_ACTION_DISP = Change Case
    -> gzFieldCalculator
gzFieldCalculator
    AddFieldsValues_Output_1 -> gzSourceTargetQA
gzSourceTargetQA
    SourceTargetQA_Output_1 -> gzWriteData
gzWriteData
    IgnoreErrors = False
    GroupBy = $(flr)
    HASERRORS = @Value(HasErrors)
    gzLogWriter -> gzLog (writer GEODATABASE_SDE_4)
    gzErrorWriter -> gzError (writer GEODATABASE_SDE_4)
    gzFeatureWriter -> TruncateFirst
gzLog (writer GEODATABASE_SDE_4)
    attributes: procname char(255), loadtime date, loadname char(255), dataset char(255), completed smallint, loaduser char(255), activeflag char(255)
TruncateFirst: TestFilter
    TEST_LIST = BOOL_OP,OR,COMPOSITE_TEST,<Unused>,TEST_CLAUSE,"TEST $(truncate) = Y",Y,BOOL_OP,OR,COMPOSITE_TEST,<Unused>,TEST_CLAUSE,"TEST $(truncate) = N",N
    DEFAULT_VALUE = <UNFILTERED>
    N -> NewFeatureType (writer GEODATABASE_SDE_4)
    Y -> NewFeatureType00 (writer GEODATABASE_SDE_4)
NewFeatureType00 (writer GEODATABASE_SDE_4)
NewFeatureType (writer GEODATABASE_SDE_4)
gzError (writer GEODATABASE_SDE_4)
    attributes: procname char(255), sourcename char(255), srcidfield char(255), srcidval char(255), dataset char(255), reason char(255), erruser char(255), errtime date, activeflag char(255)
gseOutlineFloorPoint: gseFloorPoint

FME custom transformer gseGetBldgFloorInfo

Parameters:
- flr = UWS_1002_01   # Floor ID
- bldg =   # Building ID

TestFilter_2_Input (input)
    -> AttributeExposer
AttributeExposer
    ATTR_LIST = floorid,buildingid,schelev,fme_feature_type,floor,siteid,calcrot,floor_name,floor_level
    -> TestFilter_2
TestFilter_2
    TEST_LIST = BOOL_OP,OR,COMPOSITE_TEST,<Unused>,TEST_CLAUSE,"TEST @Value(fme_feature_type) = Building_Outline_Tilt",Building_Outline_Tilt,BOOL_OP,OR,COMPOSITE_TEST,<Unused>,TEST_CLAUSE,"TEST @Value(fme_feature_type) = Building_Outline_Point",Building_Outline_Point,BOOL_OP,OR,COMPOSITE_TEST,<Unused>,TEST_CLAUSE,"TEST @Value(fme_feature_type) = Active_Floor",Active_Floor,BOOL_OP,OR,COMPOSITE_TEST,<Unused>,TEST_CLAUSE,"TEST @Value(fme_feature_type) = Floor_Level",Floor_Level
    DEFAULT_VALUE = <UNFILTERED>
    Floor_Level -> FeatureMerger_3 [input 2]
    Building_Outline_Tilt -> BoundsExtractor
    Active_Floor -> TestFilterBldg
    Building_Outline_Point -> GeometryExtractor
BoundsExtractor
    YMIN = _ymin
    ZMIN = _zmin
    XMIN = _xmin
    XMAX = _xmax
    ZMAX = _zmax
    YMAX = _ymax
    -> LengthCalculator
LengthCalculator
    LEN_ATTR = _bldg_outline_length
    MULT = 1
    DIM = 2
    -> FeatureMerger_4 [input 1]
GeometryExtractor
    ATTR = _geometry
    KIND_LONG = FME Binary
    -> FeatureMerger_4 [input 2]
FeatureMerger_4
    PROCESS_DUPS = No
    MERGE_TYPE = Attributes Only
    SUPPLIERS_FIRST = No
    JOIN_KEYS = @Value(buildingid) @Value(buildingid) AUTO
    SUPPLIER_PREFIX_DUMMY = YES
    MERGED -> FeatureMerger_2 [input 1]
TestFilterBldg
    TEST_LIST = BOOL_OP,OR,COMPOSITE_TEST,<Unused>,TEST_CLAUSE,"TEST $(flr) BEGINS_WITH @Value(buildingid)",bldgid
    DEFAULT_VALUE = <UNFILTERED>
    bldgid -> ListBuilder_2
ListBuilder_2
    LIST_NAME = _floors
    GRP_BY = buildingid
    -> sortScheleve
sortScheleve: ListSorter
    TYPE = Numeric
    SRC_LIST = _floors{}.schelev
    ORDER = Increasing
    -> ListExploder_2
ListExploder_2
    INDEX_ATTR = _stack_index
    MODE = List Elements and Original Attributes
    LIST_ATTR = _floors{}
    LIST_FOUND -> Tester_2
    LIST_FOUND -> ListExploder_2_ListFound
Tester_2
    TEST_MODE = Automatic
    TEST_DESCRIPTION = ""
    BOOL_OP = OR
    TEST_CLAUSE = TEST @Value(floorid) = $(flr)
    PASSED -> AttributeCopier
AttributeCopier
    ATTR_LIST = _stack_index,stacklevel,""
    -> FeatureMerger_2 [input 2]
FeatureMerger_2
    PROCESS_DUPS = No
    MERGE_TYPE = Attributes Only
    SUPPLIERS_FIRST = No
    JOIN_KEYS = @Value(buildingid) @Value(buildingid) AUTO
    SUPPLIER_PREFIX_DUMMY = YES
    MERGED -> FeatureMerger_3 [input 1]
FeatureMerger_3
    PROCESS_DUPS = No
    MERGE_TYPE = Attributes Only
    SUPPLIERS_FIRST = No
    JOIN_KEYS = @Value(floor) @Value(floor) AUTO
    SUPPLIER_PREFIX_DUMMY = YES
    MERGED -> FeatureMerger_3_Merged (output)
FeatureMerger_3_Merged (output)
ListExploder_2_ListFound: Inspector [off]

FME custom transformer gzTiltRooms
Tilt Rooms in floorplans to create a pseudo-isometric view of the rooms and floors

Parameters:
- pFLOORID = UWS_1002_02   # Enter the Floor ID
- tiltHeight = 2   # Tilt height - 2 will tilt 50%

INPUT (input)
    -> AttributeCopier_3_Output
    -> Rotation
Note: Function will rotate flat/horizontal. Add 15 degrees
Rotation: ExpressionEvaluator
    VAL_ATTR = CALCULATED_ROTATION
    EXPRESSION = @Value(calcrot) + 15
    -> Rotator
Rotator
    YORIG = @Value(_ymin)
    ANGLE = @Value(CALCULATED_ROTATION)
    XORIG = @Value(_xmin)
    ROTATED -> Y_Base
Note: Add 40 meters to the base of every point * stacklevel + building height
Y_Base: ExpressionEvaluator
    VAL_ATTR = _yBase
    EXPRESSION = @Value(_ymin) + (@Value(stacklevel)  * @Value(spacing)  * 30 * (@Value(_bldg_outline_length) / @abs(@Value(_ymax) - @Value(_ymin))/$(tiltHeight)))
    -> tiltFactor
Note: height reduction 2 * spacing=1 will be 50% tilted
tiltFactor: ExpressionEvaluator
    VAL_ATTR = _tiltFactor
    EXPRESSION = "@Value(spacing) * $(tiltHeight)\n\n"
    -> Chopper
Chopper
    MAX = 1
    CHOPPED -> CoordinateExtractor
CoordinateExtractor
    Y_ATTR = _y
    X_ATTR = _x
    Z_DEFAULT = -9999
    Z_ATTR = _z
    IND = 0
    -> tilt_y
Note: calc tilted y value for each point
tilt_y: ExpressionEvaluator
    VAL_ATTR = _tiltY
    EXPRESSION = @Value(_yBase) + ((@Value(_y) - @Value(_ymin)) / @Value(_tiltFactor)) * (1 - @Value(margin))
    -> 2DPointReplacer
2DPointReplacer
    XVALATTR = @Value(_x)
    YVALATTR = @Value(_tiltY)
    POINT -> PointConnector
PointConnector
    BREAKATTR = spaceid
    POLYGON -> GeometryCoercer_2
    LINE -> GeometryCoercer_2
GeometryCoercer_2
    CHECKZ = No
    KIND = fme_polygon
    COERCED -> SelfIntersectChecker_2
SelfIntersectChecker_2
    SelfIntersecting -> Logger_SelfIntersecting
    NotSelfIntersecting -> OUTPUT (output)
OUTPUT (output)
Logger_SelfIntersecting
    MESSAGE = Feature is:
    MAXFEATS = 20
    MAXCOORDS = 20
AttributeCopier_3_Output: Inspector [off]

FME custom transformer gseFloorplanCounts
Count floorplan features for floor

Parameters:
- BUILDINGID = @Value(buildingid)   # buildingid
- FLOORID = @Value(floorid)   # floorid
- FME_FEATURE_TYPE = @Value(fme_feature_type)   # Fme Feature Type

AttributeCopier_Input (input)
    -> AttributeCopier
AttributeCopier
    ATTR_LIST = buildingid,_buildingid,"",floorid,_floorid,""
    -> TestFilter
TestFilter
    TEST_LIST = BOOL_OP,OR,COMPOSITE_TEST,<Unused>,TEST_CLAUSE,"TEST @Value(fme_feature_type) = Floor_Area",Floor_Area,BOOL_OP,OR,COMPOSITE_TEST,<Unused>,TEST_CLAUSE,"TEST @Value(fme_feature_type) = InteriorSpace",InteriorSpace,BOOL_OP,OR,COMPOSITE_TEST,<Unused>,TEST_CLAUSE,"TEST @Value(fme_feature_type) = FloorplanLine",FloorplanLine
    DEFAULT_VALUE = <UNFILTERED>
    FloorplanLine -> StatisticsCalculator
    InteriorSpace -> StatisticsCalculator_2
    Floor_Area -> StatisticsCalculator_3
StatisticsCalculator_3
    COMPUTE_HISTOGRAM = NO
    STATS_ATTRS = floorid
    COUNT_ATTR = hasfloorareas
    NUMERIC_ATTR = _numeric_count
    MIN_ATTR = _floorid
    PREPEND_ATTR_NAME_CHOICE = Automatically
    SUMMARY -> FeatureMerger_5 [input 1]
StatisticsCalculator_2
    COMPUTE_HISTOGRAM = NO
    STATS_ATTRS = floorid
    COUNT_ATTR = hasinteriorspaces
    NUMERIC_ATTR = _numeric_count
    MIN_ATTR = _floorid
    PREPEND_ATTR_NAME_CHOICE = Automatically
    SUMMARY -> FeatureMerger_5 [input 2]
FeatureMerger_5
    PROCESS_DUPS = No
    MERGE_TYPE = Attributes Only
    SUPPLIERS_FIRST = No
    JOIN_KEYS = @Value(_floorid) @Value(_floorid)
    SUPPLIER_PREFIX_DUMMY = YES
    MERGED -> FeatureMerger_6 [input 1]
    NOT_MERGED -> FeatureMerger_6 [input 1]
    UNREFERENCED -> FeatureMerger_6 [input 1]
StatisticsCalculator
    COMPUTE_HISTOGRAM = NO
    STATS_ATTRS = floorid
    COUNT_ATTR = hasfloorplanlines
    NUMERIC_ATTR = _numeric_count
    MIN_ATTR = _floorid
    PREPEND_ATTR_NAME_CHOICE = Automatically
    SUMMARY -> FeatureMerger_6 [input 2]
FeatureMerger_6
    PROCESS_DUPS = No
    MERGE_TYPE = Attributes Only
    SUPPLIERS_FIRST = No
    JOIN_KEYS = @Value(_floorid) @Value(_floorid)
    SUPPLIER_PREFIX_DUMMY = YES
    MERGED -> FeatureMerger_6_Merged (output)
    NOT_MERGED -> FeatureMerger_6_NotMerged (output)
    UNREFERENCED -> FeatureMerger_6_Unreferenced (output)
FeatureMerger_6_Merged (output)
FeatureMerger_6_NotMerged (output)
FeatureMerger_6_Unreferenced (output)

FME custom transformer gzSetupExtract

INPUT (input)
    -> AttributeExposer
AttributeExposer
    ATTR_LIST = fme_feature_type_name
    -> PythonCaller
PythonCaller
    PYTHONSOURCE:
      import fmeobjects


      # Template Function interface:
      def processFeature(feature):
          pass

      # Template Class Interface:
      class FeatureProcessor(object):
          def __init__(self):
              pass
          def input(self,feature):
              whereClause = ""
              featType = feature.getAttribute("fme_feature_type_name")
              for sourceDataset in sourceDatasets:
                  sourceName = sourceDataset.getAttributeNode("sourceName").nodeValue
                  if debug == True:
                      logger.logMessageString("gz sources=" + featType + "|" + sourceName)
                  if sourceName == featType:
                      whereClause = getWhereClause(featType)
                      if debug == True:
                          logger.logMessageString("gz Where=" + whereClause)
                      feature.setAttribute("WhereClause",whereClause)
                      self.pyoutput(feature)

          def close(self):
              pass
    PYTHONSYMBOL = FeatureProcessor
    NEW_ATTRIBUTES = WhereClause *
    -> OUTPUT (output)
OUTPUT (output)

FME custom transformer gzBuildingAngle

Parameters:
- BUILDINGID =   # Enter the Building ID

INPUT (input)
    -> Chopper_2
    -> FeatureMerger_3 [input 1]
Chopper_2
    MAX = 2
    CHOPPED -> LengthCalculator_2
LengthCalculator_2
    LEN_ATTR = _length
    MULT = 1
    DIM = 2
    -> StatisticsCalculator_2
StatisticsCalculator_2
    STATS_ATTR = _length
    PASS_THROUGH = Yes
    MAX_ATTR = _max
    RANGE_ATTR = _range
    SUM_ATTR = _sum
    COUNT_ATTR = _count
    NUMERIC_ATTR = _numeric_count
    STDEV_ATTR = _stdev
    MODE_ATTR = _mode
    MEDIAN_ATTR = _median
    MIN_ATTR = _min
    MEAN_ATTR = _mean
    STATISTICS -> TestFilter_6
TestFilter_6
    TEST_LIST = BOOL_OP,OR,COMPOSITE_TEST,<Unused>,TEST_CLAUSE,"TEST ""@Value(_length)"" = ""@Value(_max)""",_length = _max
    DEFAULT_VALUE = <UNFILTERED>
    _length = _max -> CoordinateExtractor_4
CoordinateExtractor_4
    Y_ATTR = _y1
    X_ATTR = _x1
    Z_DEFAULT = -9999
    Z_ATTR = _z
    IND = 0
    -> CoordinateExtractor_6
CoordinateExtractor_6
    Y_ATTR = _y2
    X_ATTR = _x2
    Z_DEFAULT = -9999
    Z_ATTR = _z
    IND = 1
    -> TestFilter_4
TestFilter_4
    TEST_LIST = BOOL_OP,OR,COMPOSITE_TEST,<Unused>,TEST_CLAUSE,"TEST ""@Value(_y2)"" >= ""@Value(_y1)""",_y2 >= _y1
    DEFAULT_VALUE = <UNFILTERED>
    _y2 >= _y1 -> ExpressionEvaluator_7
    <UNFILTERED> -> ExpressionEvaluator_4
Note: Calculate angle of the longest side
ExpressionEvaluator_7
    VAL_ATTR = _angle
    EXPRESSION = @atan2(@Value(_x1)-@Value(_x2),@Value(_y1)-@Value(_y2))*180.0/(22/7.0)
    -> ExpressionEvaluator_8
ExpressionEvaluator_4
    VAL_ATTR = _angle
    EXPRESSION = @atan2(@Value(_x2)-@Value(_x1),@Value(_y2)-@Value(_y1))*180.0/(22/7.0)
    -> ExpressionEvaluator_8
ExpressionEvaluator_8
    VAL_ATTR = _angle
    EXPRESSION = @Value(_angle) + 90.0
    -> TestFilter_5
TestFilter_5
    TEST_LIST = BOOL_OP,OR,COMPOSITE_TEST,<Unused>,TEST_CLAUSE,"TEST ""@Value(_angle)"" > ""180.0""",_angle > 180.0
    DEFAULT_VALUE = <UNFILTERED>
    _angle > 180.0 -> ExpressionEvaluator_10
    <UNFILTERED> -> Sorter_2
ExpressionEvaluator_10
    VAL_ATTR = _angle
    EXPRESSION = @Value(_angle) -180.0
    -> Sorter_2
Sorter_2
    SORT_PARM = _length NUMERIC DESCENDING
    SORTED -> FeatureMerger_3 [input 2]
FeatureMerger_3
    BUILD_INCOMPLETE = No
    PROCESS_DUPS = No
    MERGE_TYPE = Attributes Only
    REFERATTR = $(BUILDINGID)
    REFEEATTR = $(BUILDINGID)
    COMPLETE -> GeometryExtractor_2
GeometryExtractor_2
    ATTR = _geometry
    KIND_LONG = FME Binary
    -> CenterOfGravityReplacer
CenterOfGravityReplacer
    CENTEROFGRAVITY -> CoordinateExtractor_3
CoordinateExtractor_3
    Y_ATTR = YCENTER
    X_ATTR = XCENTER
    Z_DEFAULT = -9999
    Z_ATTR = _z
    IND = 0
    -> GeometryReplacer
GeometryReplacer
    ATTR = _geometry
    KIND_LONG = FME Binary
    -> AttributeCreator
Note: Calculate X and Y Center Point
AttributeCreator
    ATTR_LIST = MODANGLE,0,SPACING,50,MARGIN,.2,HULLROT,@Value(_angle)
    -> OUTPUT (output)
OUTPUT (output)

FME custom transformer gseFloorPointAttrs
Get building and floor attributes for floor points

Parameters:
- GEODB_OID = @Value(geodb_oid)   # Geodb Oid
- OBJECTID = @Value(objectid)   # objectid
- SITEID = @Value(siteid)   # siteid
- BUILDINGID = @Value(buildingid)   # buildingid
- FLOOR = @Value(floor)   # floor
- FLOORID = @Value(floorid)   # floorid
- FLOOR_AREA = @Value(floor_area)   # Floor Area
- SCHELEV = @Value(schelev)   # schelev
- ALTITUDE = @Value(altitude)   # altitude
- SENSITIVITY = @Value(sensitivity)   # sensitivity
- SOURCEDWG = @Value(sourcedwg)   # sourcedwg
- IN_DATE = @Value(in_date)   # In Date
- LAST_USER = @Value(last_user)   # Last User
- GLOBALID = @Value(globalid)   # globalid
- FLOOR_NAME = @Value(floor_name)   # Floor Name
- BLDG_NAME = @Value(bldg_name)   # Bldg Name
- SHAPE.STAREA__ = @Value(shape.starea())   # shape.starea()
- SHAPE.STLENGTH__ = @Value(shape.stlength())   # shape.stlength()
- DRAWING = @Value(drawing)   # drawing
- FME_FEATURE_TYPE = @Value(fme_feature_type)   # Fme Feature Type
- SPACEID = @Value(spaceid)   # spaceid

FeatureReader_3_Initiator (input)
    -> FeatureReader_3
FeatureReader_3
    GEODATABASE_SDE_RESOLVE_SUBTYPE_NAMES = yes
    GEODATABASE_SDE_SPLIT_COMPLEX_EDGES = no
    FEATURETYPES = Active_Floor Building_Outline_Point Building_Outline_Tilt Floor_Level
    GEODATABASE_SDE_VERSION = dbo.DEFAULT
    GEODATABASE_SDE_TRANSLATE_SPATIAL_DATA_ONLY = no
    GEODATABASE_SDE_CONNECTION = Connection File
    COMBINE_GEOM = Keep result geometry only
    GEODATABASE_SDE_VERSION_TYPE = Connect using a Transactional Version
    COMBINE_ATTRS = In case of conflict, keep result attributes
    GEODATABASE_SDE_REMOVE_TABLE_QUALIFIER = YES
    GEODATABASE_SDE_IGNORE_RELATIONSHIP_INFO = yes
    SUPPORTED_SPATIAL_INTERACTIONS = ENVELOPE_INTERSECT%INTERSECTS%CONTAINS%CROSSES%DISJOINT%EQUALS%OVERLAPS%TOUCHES%WITHIN
    DATASET = sde
    GEODATABASE_SDE_TABLELIST = Floor_Level Active_Floor Building_Outline_Tilt Building_Outline_Point
    GEODATABASE_SDE_SPLIT_MULTI_PART_ANNOS = no
    ATTRIBUTES = Active_Floor,"geodb_oid,OBJECTID,BUILDINGID,FLOOR,FLOORID,DWG_NAME,INTERIORSPACE,FLOORPLANLINE,SCHELEV,ALTITUDE,GlobalID",Building_Outline_Point,"geodb_oid,OBJECTID,SITEID,BUILDINGID,CALCROT,NUMFLOORS,SOURCEDWG,SCALE_85X11,SCALE_11X17,SENSITIVITY,IN_DATE,LAST_USER,GlobalID",Building_Outline_Tilt,"geodb_oid,OBJECTID,SITEID,BUILDINGID,BLDGHEIGHT,SPACING,MARGIN,XCENTER,YCENTER,CALCROT,SOURCEID,SOURCEDWG,SENSITIVITY,IN_DATE,LAST_USER,GlobalID,SHAPE.STArea(),SHAPE.STLength()",Floor_Level,"geodb_oid,OBJECTID,FLOOR,FLOOR_LEVEL,NAME_LONG,NAME_SHORT,GlobalID"
    GEODATABASE_SDE_RESOLVE_DOMAINS = no
    GEODATABASE_SDE_FEATURE_READ_MODE = Features
    FORMAT = GEODATABASE_SDE
    GEODATABASE_SDE_CONNECTION_FILE = C:\apps\Gizinta\gseVT\ETL\serverConfig\GIS Production.sde
    GEODATABASE_SDE_IGNORE_NETWORK_INFO = yes
    Active_Floor -> BulkAttributeRenamer_3
    Building_Outline_Tilt -> BulkAttributeRenamer_2
    Floor_Level -> BulkAttributeRenamer
    Building_Outline_Point -> GeometryExtractor
    INITIATOR -> FeatureMerger [input 1]
BulkAttributeRenamer_3
    CASE_CHANGE_TYPE = lowercase
    ATTRCHOICE = All Attributes
    PATTERN_ACTION_DISP = Change Case
    -> FeatureMerger [input 2]
FeatureMerger
    PROCESS_DUPS = No
    MERGE_TYPE = Attributes Only
    SUPPLIERS_FIRST = No
    JOIN_KEYS = @Value(floorid) @Value(floorid)
    SUPPLIER_PREFIX_DUMMY = YES
    MERGED -> FeatureMerger_3 [input 1]
GeometryExtractor
    ATTR = _geometry
    KIND_LONG = FME Binary
    -> BulkAttributeRenamer_4
BulkAttributeRenamer_4
    CASE_CHANGE_TYPE = lowercase
    ATTRCHOICE = All Attributes
    PATTERN_ACTION_DISP = Change Case
    -> FeatureMerger_3 [input 2]
FeatureMerger_3
    PROCESS_DUPS = No
    MERGE_TYPE = Attributes Only
    SUPPLIERS_FIRST = No
    JOIN_KEYS = @Value(buildingid) @Value(buildingid) AUTO
    SUPPLIER_PREFIX_DUMMY = YES
    MERGED -> FeatureMerger_7 [input 1]
BulkAttributeRenamer_2
    CASE_CHANGE_TYPE = lowercase
    ATTRCHOICE = All Attributes
    PATTERN_ACTION_DISP = Change Case
    -> FeatureMerger_7 [input 2]
FeatureMerger_7
    PROCESS_DUPS = No
    MERGE_TYPE = Attributes Only
    SUPPLIER_PREFIX = _tilt
    SUPPLIERS_FIRST = No
    JOIN_KEYS = @Value(buildingid) @Value(buildingid)
    SUPPLIER_PREFIX_DUMMY = YES
    MERGED -> FeatureMerger_2 [input 1]
BulkAttributeRenamer
    CASE_CHANGE_TYPE = lowercase
    ATTRCHOICE = All Attributes
    PATTERN_ACTION_DISP = Change Case
    -> FeatureMerger_2 [input 2]
FeatureMerger_2
    PROCESS_DUPS = No
    MERGE_TYPE = Attributes Only
    SUPPLIER_PREFIX = _floorlevel
    SUPPLIERS_FIRST = No
    JOIN_KEYS = @Value(floor) @Value(floor)
    SUPPLIER_PREFIX_DUMMY = YES
    MERGED -> FeatureMerger_2_Merged (output)
FeatureMerger_2_Merged (output)

FME custom transformer gzFixIntersections

Parameters:
- Tolerance = 0.001   # Generalization tolerance
- UniqueIDName = SPACEID   # UniqueID field name for polygons
- Feature_Type = InteriorSpace_All   # Feature Type to process

INPUT (input)
    -> AttributeExposer
AttributeExposer
    ATTR_LIST = fme_feature_type,DRAWING,BUILDINGID,FLOORID
    -> StringReplacer
StringReplacer
    SRC_ATTRS = fme_feature_type
    REGEXP = no
    CASE = no
    NO_MATCH = _FME_NO_OP_
    FIND_TEXT = DBO.
    -> Tester
Tester
    TEST_MODE = Automatic
    TEST_DESCRIPTION = ""
    BOOL_OP = OR
    TEST_CLAUSE = TEST @Value(fme_feature_type) = $(Feature_Type)
    PASSED -> Generalizer
Generalizer
    ALG_TEXT = Douglas (Generalize)
    PRESERVE = No
    TOLERANCE = $(Tolerance)
    -> GeometryValidator
GeometryValidator
    CHECK_HOLE_TOUCHING_POLYGON = No
    DUP_COORDS_CHECK_Z = Yes
    NULL_REMOVAL = NULL_REMOVAL
    SELF_INTERSECTING = SELF_INTERSECTING
    PRESETS = Custom
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    REPAIR = Yes
    ISSUE_ATTR_NAME = _issues
    PLANAR_TOLERANCE_MODE = Auto
    NAN_REMOVAL = NAN_REMOVAL
    CONSECUTIVE_IDENTICAL_VERTICES_2D = CONSECUTIVE_IDENTICAL_VERTICES_2D
    PASSED -> GeometryCoercer_2
    REPAIRED -> GeometryCoercer_2
GeometryCoercer_2
    CHECKZ = No
    KIND = fme_polygon
    COERCED -> SelfIntersectChecker_2
SelfIntersectChecker_2
    SelfIntersecting -> Logger_SelfIntersecting
    NotSelfIntersecting -> OUTPUT (output)
OUTPUT (output)
Logger_SelfIntersecting
    MESSAGE = Feature is self-intersecting:
    MAXFEATS = 100
    MAXCOORDS = 20

FME custom transformer gseFloorPoint

INPUT (input)
BulkAttributeRenamer_5
    CASE_CHANGE_TYPE = lowercase
    ATTRCHOICE = All Attributes
    PATTERN_ACTION_DISP = Change Case
    -> Tester
Tester
    TEST_MODE = Automatic
    TEST_DESCRIPTION = ""
    BOOL_OP = OR
    TEST_CLAUSE = TEST @Value(fme_feature_type) = Floor_Area
    PASSED -> gseFloorPointAttrs
gseFloorPointAttrs
    ALTITUDE = @Value(altitude)
    FLOOR = @Value(floor)
    GLOBALID = @Value(globalid)
    IN_DATE = @Value(in_date)
    FLOOR_NAME = @Value(floor_name)
    SCHELEV = @Value(schelev)
    SENSITIVITY = @Value(sensitivity)
    SOURCEDWG = @Value(sourcedwg)
    LAST_USER = @Value(last_user)
    SITEID = @Value(siteid)
    SPACEID = @Value(spaceid)
    GEODB_OID = @Value(geodb_oid)
    BUILDINGID = @Value(buildingid)
    DRAWING = @Value(drawing)
    FLOOR_AREA = @Value(floor_area)
    SHAPE.STAREA__ = @Value(shape.starea())
    OBJECTID = @Value(objectid)
    FLOORID = @Value(floorid)
    FME_FEATURE_TYPE = @Value(fme_feature_type)
    SHAPE.STLENGTH__ = @Value(shape.stlength())
    BLDG_NAME = @Value(bldg_name)
    FeatureMerger_2_Merged -> AttributeExposer
    FeatureMerger_2_Merged -> gseFloorplanCounts
AttributeExposer
    ATTR_LIST = geodb_feature_dataset
    -> StringReplacer
    -> AttributeExposer_Output
AttributeExposer_Output: Inspector
StringReplacer
    SRC_ATTRS = geodb_feature_dataset
    REGEXP = no
    CASE = no
    REPLACE_TEXT = .Floorplan
    NO_MATCH = _FME_NO_OP_
    FIND_TEXT = .Basemap
    -> AttributeCreator
AttributeCreator
    ATTR_LIST = fme_feature_type,Floor_Point,localrot,@Value(_tiltcalcrot),floor_level,@Value(_floorlevelfloor_level),floor_name,@Value(_floorlevelname_short),floor_name_1,@Value(_floorlevelname_long)
    -> GeometryReplacer
GeometryReplacer
    SOURCE = @Value(_geometry)
    REMOVE_ATTRIBUTE = No
    KIND_LONG = FME Binary
    -> OUTPUT (output)
OUTPUT (output)
gseFloorplanCounts
    FLOORID = @Value(floorid)
    FME_FEATURE_TYPE = @Value(fme_feature_type)
    BUILDINGID = @Value(buildingid)
    FeatureMerger_6_Merged -> gseFloorplanCounts_FeatureMerger_6_Merged
    FeatureMerger_6_NotMerged -> gseFloorplanCounts_FeatureMerger_6_Merged
    FeatureMerger_6_Unreferenced -> gseFloorplanCounts_FeatureMerger_6_Merged
gseFloorplanCounts_FeatureMerger_6_Merged: Inspector

FME custom transformer SelfIntersectChecker
Separates self-intersecting features from the rest of input. This custom transformer does not change the geometry of self-intersecting features. If you want to remove self-intersections, try the " SelfIntersector " transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Input (input)
    -> PartCounter
PartCounter
    COUNT_ATTR = _part_count1
    RECURSIVE_PARAM = No
    -> COUNTER
COUNTER: Counter
    SCOPE = Local
    START = 0
    DOMAIN = counter
    CNT_ATTR = _selfID
    -> GeometryExtractor
GeometryExtractor
    OGCVERSION = 1.2
    ATTR = _geometry
    KIND_LONG = OGC Well Known Text
    -> SelfIntersector
SelfIntersector
    SEG_ATTR = _segments
    SELF_INTERSECTED -> DuplicateRemover
DuplicateRemover
    KEYATTR = _selfID
    UNIQUE -> TESTER
TESTER: Tester
    TEST_MODE = NUMERIC
    BOOL_OP = OR
    TEST_LIST = &_segments,>,1
    TEST_CLAUSE = TEST @Value(_segments) > 1
    FAILED -> PartCounter_2
    PASSED -> GeometryReplacer
PartCounter_2
    COUNT_ATTR = _part_count2
    RECURSIVE_PARAM = No
    -> TESTER_2
TESTER_2: Tester
    TEST_MODE = Automatic
    BOOL_OP = OR
    TEST_LIST = &_part_count1,=,&_part_count2
    TEST_CLAUSE = TEST @Value(_part_count1) = @Value(_part_count2)
    PASSED -> ATTRIBUTEREMOVER
    FAILED -> GeometryReplacer
ATTRIBUTEREMOVER: AttributeRemover
    REMOVE_ATTRS = _selfID,_geometry,_segments
    -> NotSelfIntersecting (output)
NotSelfIntersecting (output)
GeometryReplacer
    ATTR = _geometry
    KIND_LONG = OGC Well Known Text
    -> ATTRIBUTEREMOVER_2
ATTRIBUTEREMOVER_2: AttributeRemover
    REMOVE_ATTRS = _selfID,_geometry,_segments
    -> SelfIntersecting (output)
SelfIntersecting (output)

FME custom transformer gzAggregateLines
Clean geometries and Aggregate Floorplan lines into _Optimized features

INPUT (input)
    -> CoordinateCounter
CoordinateCounter
    CNT_ATTR = _coordcount
    -> LengthCalculator_2
LengthCalculator_2
    LEN_ATTR = _length
    MULT = 1
    DIM = 2
    -> TestFilter_6
TestFilter_6
    TEST_LIST:
      BOOL_OP,AND,COMPOSITE_TEST,<Unused>,TEST_CLAUSE,"TEST ""@Value(_coordcount)"" >= ""2""
      TEST ""@Value(_length)"" >= "".001""",2pts & length > .01
    DEFAULT_VALUE = <UNFILTERED>
    2pts & length > .01 -> GeometryCoercer_2
GeometryCoercer_2
    KIND = fme_line
    COERCED -> GeometryFilter
GeometryFilter
    BREAK_AGG = No
    LINE -> SelfIntersector
    ARC -> SelfIntersector
SelfIntersector
    SEG_ATTR = _segments
    SELF_INTERSECTED -> GeometryCoercer
GeometryCoercer
    KIND = fme_line
    COERCED -> LengthCalculator
LengthCalculator
    LEN_ATTR = _length
    MULT = 1
    DIM = 2
    -> Tester
Tester
    TEST_MODE = Automatic
    TEST_DESCRIPTION = ""
    BOOL_OP = OR
    TEST_CLAUSE = TEST @Value(_length) > .1
    PASSED -> GeometryFilter_2
GeometryFilter_2
    BREAK_AGG = No
    ARC -> SelfIntersector_2
    LINE -> SelfIntersector_2
SelfIntersector_2
    SEG_ATTR = _segments
    SELF_INTERSECTED -> GeometryCoercer_3
GeometryCoercer_3
    KIND = fme_line
    COERCED -> LengthCalculator_3
LengthCalculator_3
    LEN_ATTR = _length
    MULT = 1
    DIM = 2
    -> Tester_2
Tester_2
    TEST_MODE = Automatic
    TEST_DESCRIPTION = ""
    BOOL_OP = OR
    TEST_CLAUSE = TEST @Value(_length) > .1
    PASSED -> Aggregator_2
Aggregator_2
    GROUP_BY = floorid
    SEP = ,
    CONTAIN_INDIVID_GEOMS = No
    ACCUM_ATTRS_NAME = Yes
    ORDERED = No
    AGGREGATE -> OUTPUT (output)
OUTPUT (output)
